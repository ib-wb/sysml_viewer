// Beispielprojekt Indoorroboter – Disziplinen als Metadaten
// Anwenden mit #Disziplin vor einer Definition, z. B. #Mechanik part def Rad
package Disziplinen {
    metadata def Mechanik;
    metadata def Elektronik;
    metadata def Software;
}
