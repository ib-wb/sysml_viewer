// Sample project indoor robot – disciplines as metadata
// Apply with #Discipline in front of a definition, e.g. #Mechanics part def Wheel
package Disciplines {
    metadata def Mechanics;
    metadata def Electronics;
    metadata def Software;
}
